module ietf-netconf-notifications {
  yang-version 1.1;
  namespace 
    "urn:ietf:params:xml:ns:yang:ietf-netconf-notifications";

  prefix nn;

  import ietf-subscribed-notifications {
    prefix sn;
  }
  
  organization "IETF NETCONF (Network Configuration) Working Group";
  contact
    "WG Web:   <http:/tools.ietf.org/wg/netconf/>
     WG List:  <mailto:netconf@ietf.org>

     Author:   Eric Voit
               <mailto:evoit@cisco.com>";

  description
    "Defines NETCONF as a supported transport for subscribed event
	notifications.";
  
  revision 2018-04-03 {
    description
      "Initial version";
    reference 
    "RFC XXXX: NETCONF Support for Event Notifications";
  }

 
  identity netconf {
    base sn:transport;
    base sn:inline-address;
    description
      "Netconf is used a transport for notification messages and state
       change notifications.";
  }
  
}
