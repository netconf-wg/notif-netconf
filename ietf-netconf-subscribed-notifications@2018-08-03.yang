module ietf-netconf-subscribed-notifications {
  yang-version 1.1;
  namespace 
    "urn:ietf:params:xml:ns:yang:ietf-netconf-subscribed-notifications";

  prefix nsn;

  import ietf-subscribed-notifications { 
    prefix sn;
  }
  import ietf-netconf-client { 
    prefix ncc; 
  }
  
  organization "IETF NETCONF (Network Configuration) Working Group";
  contact
    "WG Web:   <http:/tools.ietf.org/wg/netconf/>
     WG List:  <mailto:netconf@ietf.org>
          
     Editor:   Eric Voit
               <mailto:evoit@cisco.com>
     
     Editor:   Alexander Clemm
               <mailto:ludwig@clemm.org>";


  description
    "Defines NETCONF as a supported transport for subscribed event 
    notifications.";
  
  revision 2018-08-03 {
    description
      "Initial version";
    reference 
    "RFC XXXX: Customized Subscriptions to a Publisher's Event Streams";
  }
  
  identity netconf {
    base sn:transport;
    base sn:inline-address;
    description
      "NETCONF is used as a configured subscription transport for 
      notification messages and state change notifications.";
    reference 
      "RFC-6241: Network Configuration Protocol (NETCONF)";
  }

  augment "/sn:subscriptions/sn:subscription/sn:receivers/sn:receiver"
          + "/sn:transport" {
   when 'derived-from(../../../../transport, "nsn:netconf")';   
   description
      "This augmentation allows NETCONF specific parameters to be 
      exposed for a receiver.";
    case "netconf" {
      description
        "This case allows NETCONF specific parameters to be 
        exposed for a receiver.";   
      leaf netconf-endpoint {
        type leafref {
          path "/ncc:netconf-client/ncc:initiate/ncc:netconf-server" +
               "/ncc:endpoints/ncc:endpoint/ncc:name";
        }
        mandatory true;
        description
          "Remote client which need to initiate the NETCONF transport if 
          an existing NETCONF session from that client is not 
          available.";
      }
    }
  }

}
