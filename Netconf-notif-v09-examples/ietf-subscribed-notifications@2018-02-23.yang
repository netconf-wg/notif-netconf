module ietf-subscribed-notifications {
  yang-version 1.1;
  namespace 
    "urn:ietf:params:xml:ns:yang:ietf-subscribed-notifications";

  prefix sn;

  import ietf-yang-types {
    prefix yang;
  }
  import ietf-inet-types {
    prefix inet;
  }
  import ietf-interfaces {
    prefix if;
  }
  import ietf-network-instance {
    prefix ni;
  }
  import ietf-restconf   { 
    prefix rc;   
  }
  
  organization "IETF";
  contact
    "WG Web:   <http:/tools.ietf.org/wg/netconf/>
     WG List:  <mailto:netconf@ietf.org>
     
     Editor:   Alexander Clemm
               <mailto:ludwig@clemm.org>

     Editor:   Eric Voit
               <mailto:evoit@cisco.com>
               
     Editor:   Alberto Gonzalez Prieto
               <mailto:agonzalezpri@vmware.com>

     Editor:   Einar Nilsen-Nygaard
               <mailto:einarnn@cisco.com>

     Editor:   Ambika Prasad Tripathy
               <mailto:ambtripa@cisco.com>";

  description
    "Contains a YANG specification for subscribing to event records 
    and receiving matching content within notification messages.";
  
  revision 2018-02-23 {
    description
      "Initial version";
    reference 
      "draft-ietf-netconf-subscribed-notifications-10";
  }
  
  /*
   * FEATURES
   */
  
  feature encode-json {
    description
      "This feature indicates that JSON encoding of notification
       messages is supported.";
  }
  
  feature encode-xml {
    description
      "This feature indicates that XML encoding of notification
       messages is supported.";
  }

  feature configured {
    description
      "This feature indicates that configuration of subscription is
      supported.";
  }
  
  feature replay {
    description
      "This feature indicates that historical event record replay is 
      supported.  With replay, it is possible for past event records to 
      be streamed in chronological order.";
  }

  feature xpath {
    description
      "This feature indicates support for xpath filtering.";
    reference "http://www.w3.org/TR/1999/REC-xpath-19991116";
  }

  feature subtree {
    description
      "This feature indicates support for YANG subtree filtering.";
    reference "RFC 6241, Section 6.";
  }
  
  feature supports-vrf {
    description
      "This feature indicates a publisher supports VRF configuration
      for configured subscriptions.  VRF support for dynamic 
      subscriptions does not require this feature.";
    reference "draft-ietf-rtgwg-ni-model";
  }
  
  feature qos {
    description
      "This feature indicates a publisher supports one or more optional
      Quality of Service (QoS) features to differentiate update record
      treatment between publisher and receiver.";
  }
  
  /* 
   * EXTENSIONS
   */
   
  extension subscription-state-notification {
    description
      "This statement applies only to notifications. It indicates that 
       the notification is a subscription state notification. Therefore 
       it does not participate in a regular event stream and does not 
       need to be specifically subscribed to in order to be received.
       This statement can only occur as a substatement to the YANG
       'notification' statement."; 
  }
  
  /*
   * IDENTITIES
   */

  /* Identities for RPC and Notification errors */ 
  
  identity establish-subscription-error {
     description
      "Problem found while attempting to fulfill an 
      'establish-subscription' rpc request. "; 
  }
  
  identity modify-subscription-error {
     description
      "Problem found while attempting to fulfill a
      'modify-subscription' rpc request. "; 
  }
  
  identity delete-subscription-error {
     description
      "Problem found while attempting to fulfill either a 
      'delete-subscription' rpc request or a 'kill-subscription'
      rpc request. "; 
  }
  
  identity subscription-terminated-reason {
     description
      "Problem condition communicated to a receiver as part of absolute 
      'subscription-terminated' notification. "; 
  }
  
  identity subscription-suspended-reason {
     description
      "Problem condition communicated to a receiver as part of absolute 
      'subscription-terminated' notification. "; 
  }
  
  identity dscp-unavailable {
    base establish-subscription-error;
    description 
      "Requested DSCP marking not allocatable.";
  }

  identity filter-unavailable {
    base subscription-terminated-reason;
    description
     "Referenced filter does not exist.  This means a receiver is
     referencing a filter which doesn't exist, or to which they do not
     have access permissions.";
  }
  
  identity filter-unsupported {
    base establish-subscription-error;
    base modify-subscription-error;
    description
     "Cannot parse syntax within the filter.  This failure can be from 
     a syntax error, or a syntax too complex to be processed by the 
     publisher.";
  }

  identity history-unavailable {
    base establish-subscription-error;
    description
     "Replay request too far into the past. This means the publisher
      does store historic information for the requested stream, but
      not back to the requested timestamp.";
  }

  identity insufficient-resources {
    base establish-subscription-error;
    base modify-subscription-error;
    base subscription-suspended-reason;
    description
      "The publisher has insufficient resources to support the
       requested subscription.";
  }
  
  identity no-such-subscription {
    base modify-subscription-error;
    base delete-subscription-error;
    base subscription-terminated-reason;
    description
     "Referenced subscription doesn't exist. This may be as a result of 
      a non-existent subscription ID, an ID which belongs to another 
      subscriber, or an ID for configured subscription.";
  }

  identity replay-unsupported {
    base establish-subscription-error;
    description
     "Replay cannot be performed for this subscription. This means the
      publisher will not provide the requested historic information from
      the stream via replay to this receiver.";
  }
  
  identity stream-unavailable {
    base subscription-terminated-reason;
    description
     "Not a subscribable stream.  This means the referenced stream is 
      not available for subscription by the receiver.";
  }
  
  identity suspension-timeout {
    base subscription-terminated-reason;
    description
     "Termination of previously suspended subscription. The publisher 
      has eliminated the subscription as it exceeded a time limit for
      suspension.";
  }
  
  identity unsupportable-volume {
    base subscription-suspended-reason;
    description
      "The publisher cannot support the volume of information intended
      to be sent for an existing subscription.";
  }

  /* Identities for encodings */
  identity encodings {
    description
      "Base identity to represent data encodings";
  }
  
  identity encode-xml {
    base encodings;
    if-feature "encode-xml";
    description
      "Encode data using XML";
  }
  
  identity encode-json {
    base encodings;
    if-feature "encode-json";
    description
      "Encode data using JSON";
  }

  /* Identities for transports */
  identity transport {
    description
      "An identity that represents a the underlying mechanism for 
      passing notification messages.";
  }
  
  identity netconf {
    base transport;
    description
      "Netconf is used a transport for notification messages and state
       change notifications.";
    reference "draft-ietf-netconf-netconf-event-notifications";
  }
  
  identity http2 {
    base transport;
    description
      "HTTP2 is used a transport for notification messages and state
       change notifications.";
    reference "draft-ietf-netconf-restconf-notif-03, Sections 3.1.1" +
      "3.1.3";
  }

  identity http1.1 {
    base transport;
    description
      "HTTP1.1 is used a transport for notification messages and state
       change notifications.";
    reference "draft-ietf-netconf-restconf-notif-03, Section 3.1.2";
  }   
  
  /*
   * TYPEDEFs
   */

  typedef subscription-id {
    type uint32;
    description
      "A type for subscription identifiers.";
  }

  typedef filter-id {
    type string;
    description
      "A type to identify filters which can be associated with a 
       subscription.";
  } 
  
  typedef encoding {
    type identityref {
      base encodings;
    }
    description
      "Specifies a data encoding, e.g. for a data subscription.";
  }    
  
  typedef transport {
    type identityref {
      base transport;
    }
    description
      "Specifies protocol used to send notification messages to a
       receiver.";
  }

  typedef stream-ref {
    type string;
    // einarnn: hack
    //type leafref {
    //  path "/sn:streams/sn:stream/sn:name";
    //}
    description
      "This type is used to reference a system-provided datastream.";
  }

  typedef stream-filter-ref {
    type leafref {
      path "/sn:filters/sn:stream-filter/sn:identifier";
    }
    description
      "This type is used to reference a configured stream filter.";
  }

  /*
   * GROUPINGS
   */
   
  grouping stream-filter-elements {
    description
      "This grouping defines the base for filters applied to event 
       streams.";
    choice filter-spec {
      description
        "The content filter specification for this request.";
      anydata stream-subtree-filter {
        if-feature "subtree";
        description
          "Event stream evaluation criteria encoded in the syntax of a 
          subtree filter as defined in RFC 6241, Section 6. 
          
          The subtree filter is applied to the representation of 
          individual, delineated event records as contained within the 
          event stream.  For example, if the notification message 
          contains an instance of a notification defined in YANG, then 
          the top-level element is the name of the YANG notification.
 
          If the subtree filter returns a non-empty node set, the filter
          matches the event record, and the it is included in the 
          notification message sent to the receivers.";
        reference "RFC 6241, Section 6.";  
      }
      leaf stream-xpath-filter {
        if-feature "xpath";
        type string;
        // einarnn: hack to let yanglint validate
        // type yang:xpath1.0;
        description
          "Event stream evaluation criteria encoded in the syntax of
           an XPath 1.0 expression.

           The XPath expression is evaluated on the representation of
           individual, delineated event records as contained within
           the event stream.  For example, if the notification message
           contains an instance of a notification defined in YANG,
           then the top-level element is the name of the YANG
           notification, and the root node has this top-level element
           as the only child.

           The result of the XPath expression is converted to a
           boolean value using the standard XPath 1.0 rules.  If the
           boolean value is 'true', the filter matches the event
           record, and the it is included in the notification message
           sent to the receivers.

           The expression is evaluated in the following XPath context:

             o  The set of namespace declarations are those in scope on
                the 'xpath-filter' leaf element

             o  The set of variable bindings is empty.

             o  The function library is the core function library, and
                the XPath functions defined in section 10 in RFC 7950.

             o  The context node is the root node.";
        reference
          "http://www.w3.org/TR/1999/REC-xpath-19991116
           RFC 7950, Section 10.";

      }
    }
  } 
  
  grouping update-qos {
    description
      "This grouping describes Quality of Service information
       concerning a subscription.  This information is passed to lower
       layers for transport prioritization and treatment";
    leaf dscp {
      if-feature "qos";
      type inet:dscp;
      default "0";
      description
        "The push update's IP packet transport priority. This is made 
         visible across network hops to receiver. The transport 
         priority is shared for all receivers of a given subscription.";
    }
    leaf weighting {
      if-feature "qos";
      type uint8 {
         range "0 .. 255";
      }
      description
        "Relative weighting for a subscription. Allows an underlying 
         transport layer perform informed load balance allocations 
         between various subscriptions";
      reference 
        "RFC-7540, section 5.3.2";
    }
    leaf dependency {
      if-feature "qos";
      type subscription-id;
      description
        "Provides the Subscription ID of a parent subscription which 
         has absolute priority should that parent have push updates
         ready to egress the publisher. In other words, there should be
         no streaming of objects from the current subscription if   
         the parent has something ready to push.";
      reference 
        "RFC-7540, section 5.3.1";
    }
  }
   
  grouping subscription-policy-modifiable {
    description
      "This grouping describes all objects which may be changed
      in a subscription via an RPC.";  
    choice target {
      mandatory true;
      description
        "Identifies the source of information against which a 
        subscription is being applied, as well as specifics on the 
        subset of information desired from that source.";
      case stream {
        choice stream-filter {
          description
            "An event stream filter can be applied to a subscription.  
            That filter will come either referenced from a global list,  
            or be provided within the subscription itself.";
          case by-reference {
            description
              "Apply a filter that has been configured separately.";
            leaf stream-filter-ref {
              type stream-filter-ref;
              mandatory true;
              description
                "References an existing stream-filter which is to 
                be applied to stream for the subscription.";
            }
          }
          case within-subscription {
            description
              "Local definition allows a filter to have the same   
              lifecycle as the subscription.";
            uses stream-filter-elements;
          }
        }
      }
    }
    leaf stop-time {
      type yang:date-and-time;
      description
        "Identifies a time after which notification messages for a
        subscription should not be sent.  If stop-time is not present, 
        the notification messages will continue until the subscription 
        is terminated.  If replay-start-time exists, stop-time must be
        for a subsequent time. If replay-start-time doesn't exist, 
        stop-time must be for a future time.";
    }
  }
 
  grouping subscription-policy-dynamic {
    description
      "This grouping describes information concerning a subscription
      which can just be passed over the RPCs defined in this model.";
    leaf encoding {
      type encoding;
      mandatory true;
      description
        "The type of encoding for the subscribed data.";
    }    
    uses subscription-policy-modifiable {
      augment target/stream {
        description
          "Adds additional objects which can be modified by RPC.";
        leaf stream {
          type stream-ref;
          // einarnn: hack
          //type stream-ref {
          //  require-instance false;
          //}
          mandatory true;
          description
            "Indicates the stream of event records to be considered for
            this subscription.";
        }
        leaf replay-start-time {
          if-feature "replay";
          type yang:date-and-time;
          description
            "Used to trigger the replay feature and indicate that the 
            replay should start at the time specified.  If 
            replay-start-time is not present, this is not a replay 
            subscription and event record push should start immediately.  
            It is never valid to specify start times that are later than 
            or equal to the current time.";
        }  
      }
    }
    uses update-qos;    
  }

  grouping subscription-policy {
    description
      "This grouping describes the full set of policy information 
      concerning both dynamic and configured subscriptions, except for 
      configured receivers.";
    leaf protocol {
      if-feature "configured";
      type transport;
      mandatory true;
      description
        "This leaf specifies the transport protocol used to deliver 
        messages destined to all receivers of a subscription.";
    }    
    uses subscription-policy-dynamic; 
  }

  grouping notification-origin-info {
    description
      "Defines the sender source from which notification messages for a 
       configured subscription are sent.";
    choice notification-message-origin {
      description
        "Identifies the egress interface on the Publisher from which
         notification messages are to be sent.";
      case interface-originated {
        description
          "When notification messages to egress a specific, designated
           interface on the Publisher.";
        leaf source-interface {
          type if:interface-ref;
          description
            "References the interface for notification messages.";
        }
      }
      case address-originated {
        description
          "When notification messages are to depart from a publisher
             using specfic originating address and/or routing context
           information.";
        leaf source-vrf {
          if-feature "supports-vrf";
          type leafref {
            path "/ni:network-instances/ni:network-instance/ni:name";
          }
          description
            "VRF from which notification messages should egress a 
            publisher.";
        }
        leaf source-address {
          type inet:ip-address-no-zone;
          description
            "The source address for the notification messages.  If a
            source VRF exists, but this object doesn't, a publisher's
            default address for that VRF must be used.";
        }
      }
    }
  }

  grouping receiver-info {
    description
      "Defines where and how to get notification messages for a
      configured subscriptions to one or more targeted recipient.  This
      includes specifying the destination addressing as well as a 
      transport protocol acceptable to the receiver.";
    container receivers {
      description
        "Set of receivers in a subscription.";
      list receiver {
        key "address port";
        min-elements 1;
        description
          "A single host or multipoint address intended as a target
           for the notification messages of a subscription.";
        leaf address {
          type inet:host;
          description
            "Specifies the address for the traffic to reach a remote 
            host. One of the following must be specified: an ipv4 
            address, an ipv6 address, or a host name.";
        }
        leaf port {
          type inet:port-number;
          description
            "This leaf specifies the port number to use for messages
             destined for a receiver.";
        }
      }
    }
  }


  /*
   * RPCs
   */
   
  rpc establish-subscription {
    description
      "This RPC allows a subscriber to create (and possibly negotiate) 
       a subscription on its own behalf.  If successful, the 
       subscription remains in effect for the duration of the 
       subscriber's association with the publisher, or until the 
       subscription is terminated. In case an error occurs, or the 
       publisher cannot meet the terms of a subscription, and RPC error 
       is returned, the subscription is not created.  In that case, the 
       RPC reply's error-info MAY include suggested parameter settings 
       that would have a higher likelihood of succeeding in a subsequent 
       establish-subscription request.";
    input {
      uses subscription-policy-dynamic {
        refine "encoding" {
          mandatory false;
          description
            "The type of encoding for the subscribed data. If not
            included as part of the RPC, the encoding MUST be set by the 
            publisher to be the encoding used by this RPC.";
        }
      }
    }
  }
    

  rc:yang-data establish-subscription-error-stream {
    container establish-subscription-error-stream {
      description
        "If any 'establish-subscription' RPC parameters are 
        unsupportable against the event stream, a subscription is not 
        created and the RPC error response MUST indicate the reason 
        why the subscription failed to be created. This yang-data MAY be 
        inserted as structured data within a subscription's RPC error 
        response to indicate the failure reason.  This yang-data MUST be 
        inserted if hints are to be provided back to the subscriber.";
      leaf reason {
        type identityref {
          base establish-subscription-error;
        }
        description
          "Indicates the reason why the subscription has failed to
          be created to a targeted stream.";
        }
      leaf filter-failure-hint { 
        type string;
          description
            "Information describing where and/or why a provided filter
             was unsupportable for a subscription.";
      }
      leaf replay-start-time-hint {
        type yang:date-and-time;
          description
            "If a replay has been requested, but the requested replay
            time cannot be honored, this may provide a hint at an
            alternate time which may be supportable.";
      }
    }      
  }
  
  rpc modify-subscription {
    description
      "This RPC allows a subscriber to modify a subscription that was
       previously created using establish-subscription.  If successful,
       the changed subscription remains in effect for the duration of 
       the subscriber's association with the publisher, or until the
       subscription is again modified or terminated.  In case of an 
       error or an inability to meet the modified parameters, the 
       subscription is not modified and the original subscription
       parameters remain in effect.  In that case, the rpc error 
       MAY include error-info suggested parameter hints that would have 
       a high likelihood of succeeding in a subsequent 
       modify-subscription request.  A successful modify-subscription
       will return a suspended subscription to an active state.";
    input {
      leaf identifier {
        type subscription-id;
        description
          "Identifier to use for this subscription.";
      }
      uses subscription-policy-modifiable;   
    }
  }
  
  rc:yang-data modify-subscription-error-stream {
    container modify-subscription-error-stream {
      description
        "This yang-data MAY be provided as part of a subscription's RPC
        error response when there is a failure of a
        'modify-subscription' RPC which has been made against a 
        stream.  This yang-data MUST be used if hints are to be
        provides back to the subscriber.";
      leaf reason {
        type identityref {
          base modify-subscription-error;
        }
        description
          "Information in a modify-subscription RPC error response which 
          indicates the reason why the subscription to an event stream 
          has failed to be modified.";
      }
      leaf filter-failure-hint { 
        type string;
          description
            "Information describing where and/or why a provided filter
             was unsupportable for a subscription.";
      }
    }
  }
  
  rpc delete-subscription {
    description
      "This RPC allows a subscriber to delete a subscription that
       was previously created from by that same subscriber using the 
       establish-subscription RPC.";
    input {
      leaf identifier {
        type subscription-id;
        mandatory true;
        description
          "Identifier of the subscription that is to be deleted.
           Only subscriptions that were created using
           establish-subscription can be deleted via this RPC.";
      }
    }
  }
  
  rpc kill-subscription {
    description
      "This RPC allows an operator to delete a dynamic subscription 
      without restrictions on the originating subscriber or underlying 
      transport session.";
    input {
      leaf identifier {
        type subscription-id;
        mandatory true;
        description
          "Identifier of the subscription that is to be deleted. Only
            subscriptions that were created using establish-subscription
           can be deleted via this RPC.";
      }
    }
  }
  
  rc:yang-data delete-subscription-error {
    container delete-subscription-error {
      description
        "If a 'delete-subscription' RPC or a 'kill-subscription' RPC 
        fails, the subscription is not deleted and the RPC error 
        response MUST indicate the reason for this failure. This 
        yang-data MAY be inserted as structured data within a 
        subscription's RPC error response to indicate the failure 
        reason.";
      leaf reason {
        type identityref {
          base delete-subscription-error;
        }
        mandatory true;
        description
          "Indicates the reason why the subscription has failed to be 
          deleted.";
      }
    }
  }
  
  /*
   * NOTIFICATIONS
   */

  notification replay-completed {
    sn:subscription-state-notification;
    if-feature "replay";
    description
      "This notification is sent to indicate that all of the replay
        notifications have been sent. It must not be sent for any other
       reason.";
    leaf identifier {
      type subscription-id;
      mandatory true;
      description
        "This references the affected subscription.";
    }
  }
  
  notification subscription-completed {
    sn:subscription-state-notification;
    description
      "This notification is sent to indicate that a subscription has
       finished passing event records.";
    leaf identifier {
      type subscription-id;
      mandatory true;
      description
        "This references the gracefully completed subscription.";
    }
  }

  notification subscription-started {
    sn:subscription-state-notification;
    if-feature "configured";
    description
      "This notification indicates that a subscription has started and
        notifications are beginning to be sent. This notification shall
       only be sent to receivers of a subscription; it does not 
       constitute a general-purpose notification.";
    leaf identifier {
      type subscription-id;
      mandatory true;
      description
        "This references the affected subscription.";
    }
    uses subscription-policy {
      refine "target/stream/replay-start-time" {
         description
           "Indicates the time that a replay using for the streaming of 
           buffered event records.  This will be populated with the most 
           recent of the following: replay-log-creation-time, 
           replay-log-aged-time, replay-start-time, or the most recent 
           publisher boot time.";
      }
      refine "target/stream/stream-filter/within-subscription" {
        description 
          "Filter applied to the subscription.  If the 
          'stream-filter-ref' is populated, the filter within the
          subscription came from the 'filters' container.  Otherwise it 
          is populated in-line as part of the subscription.";
      }
    }
  }
  
  notification subscription-resumed {
    sn:subscription-state-notification;
    description
      "This notification indicates that a subscription that had
       previously been suspended has resumed. Notifications will once
       again be sent.  In addition, a subscription-resumed indicates 
       that no modification of parameters has occurred since the last
       time event records have been sent.";
    leaf identifier {
      type subscription-id;
      mandatory true;
      description
        "This references the affected subscription.";
    }
  }
  
  notification subscription-modified {
    sn:subscription-state-notification;
    description
      "This notification indicates that a subscription has been 
       modified.  Notification messages sent from this point on will 
       conform to the modified terms of the subscription.  For  
       completeness, this state change notification includes both 
       modified and non-modified aspects of a subscription.";
    leaf identifier {
      type subscription-id;
      mandatory true;
      description
        "This references the affected subscription.";
    }
    uses subscription-policy {
      refine "target/stream/stream-filter/within-subscription" {
        description 
          "Filter applied to the subscription.  If the 
          'stream-filter-ref' is populated, the filter within the
          subscription came from the 'filters' container.  Otherwise it 
          is populated in-line as part of the subscription.";
      }
    }
  }
  
  notification subscription-terminated {
    sn:subscription-state-notification;
    description
      "This notification indicates that a subscription has been
       terminated.";
    leaf identifier {
      type subscription-id;
      mandatory true;
      description
        "This references the affected subscription.";
    }
    leaf reason {
      type identityref {
        base subscription-terminated-reason;
      }
      mandatory true;
      description
        "Identifies the condition which resulted in the termination .";
    }
  }

  notification subscription-suspended {
    sn:subscription-state-notification;
    description
      "This notification indicates that a suspension of the
       subscription by the publisher has occurred.  No further
       notifications will be sent until the subscription resumes.
       This notification shall only be sent to receivers of a
       subscription; it does not constitute a general-purpose
       notification.";
    leaf identifier {
      type subscription-id;
      mandatory true;
      description
        "This references the affected subscription.";
    }
    leaf reason {
      type identityref {
        base subscription-suspended-reason;
      }
      mandatory true;
      description
        "Identifies the condition which resulted in the suspension.";
    }
  }

  /*
   * DATA NODES
   */

  container streams {
    config false;
    description
      "This container contains information on the built-in streams 
      provided by the publisher.";
    list stream {
      key "name";
      description
        "Identifies the built-in streams that are supported by the
         publisher.";
      leaf name {
        type string;
        description
          "A handle for a system-provided datastream made up of a 
          sequential set of event records, each of which is 
          characterized by its own domain and semantics.";
      }
      leaf description {
        type string;
        mandatory true;
        description
          "A description of the event stream, including such information 
           as the type of event records that are available within this 
           stream.";
      }
      leaf replay-support {
        if-feature "replay";
        type empty;
        description
          "Indicates that event record replay is available on this 
          stream.";
      }
      leaf replay-log-creation-time {
        if-feature "replay";
        type yang:date-and-time;
        description
          "The timestamp of the creation of the log used to support the 
          replay function on this stream. Note that this might be 
          earlier then the earliest available information contained in   
          the log. This object is updated if the log resets for some   
          reason. This object MUST be present if replay is supported.";
      }
      leaf replay-log-aged-time {
        if-feature "replay";
        type yang:date-and-time;
        description
          "The timestamp of the last event record aged out of the log. 
          This object MUST be present if replay is supported and any 
          event record have been aged out of the log.";
      }
    }
  }
   
  container filters {
    description
      "This container contains a list of configurable filters
       that can be applied to subscriptions.  This facilitates
       the reuse of complex filters once defined.";
    list stream-filter {
      key "identifier";
      description
        "A list of pre-positioned filters that can be applied to
        subscriptions.";
      leaf identifier {
        type filter-id;
        description
          "An identifier to differentiate between filters.";
      }
      uses stream-filter-elements;
    }
  }
  
  container subscriptions {
    description
      "Contains the list of currently active subscriptions, i.e.
       subscriptions that are currently in effect, used for subscription
       management and monitoring purposes. This includes subscriptions
       that have been setup via RPC primitives as well as subscriptions 
       that have been established via configuration.";
    list subscription {
      key "identifier";
      description
        "The identity and specific parameters of a subscription. 
         Subscriptions within this list can be created using a control
         channel or RPC, or be established through configuration.";
      leaf identifier {
        type subscription-id;
        description
          "Identifier of a subscription; unique within a publisher";
      }
      leaf configured-subscription-state {
        if-feature "configured";
        type enumeration {
          enum valid {
            value 1;
            description
              "Connection is active and healthy.";
          }
          enum invalid {
            value 2;
            description
              "The subscription as a whole is unsupportable with its 
              current parameters.";
          }
          enum concluded {
            value 3;
              description
                "A subscription is inactive as it has hit a stop time, 
                but not yet been removed from configuration.";
          }
        }
        config false;
        description
          "The presence of this leaf indicates that the subscription
          originated from configuration, not through a control channel 
          or RPC.  The value indicates the system established state
          of the subscription.";
      }
      leaf purpose {
        if-feature "configured";
        type string;
        description
          "Open text allowing a configuring entity to embed the 
          originator or other specifics of this subscription.";
      }
      uses subscription-policy {
        refine "target/stream/stream" {
          description
            "Indicates the stream of event records to be considered for
            this subscription.   If a stream has been removed, and no 
            longer can be referenced by an active subscription, send a 
            'subscription-terminated' notification with 
            'stream-unavailable' as the reason.  If a configured 
            subscription refers to a non-existent stream, move that
            subscription to the 'invalid' state.";
        }
      }
      uses notification-origin-info {
        if-feature "configured";
      }
      uses receiver-info {
        augment receivers/receiver {
          description
            "include operational data for receivers.";
          leaf pushed-notifications {
            type yang:counter64;
            config false;
            description
              "Operational data which provides the number of update
               notification messages pushed to a receiver.";
            } 
          leaf excluded-notifications {
            type yang:counter64;
            config false;
            description
              "Operational data which provides the number of event
               records from a stream explicitly removed via filtering so
               that they are not sent to a receiver.";
            }
          leaf state {
            type enumeration {
              enum active {
                value 1;
                description
                  "Receiver is currently being sent any applicable 
                  notification messages for the subscription.";
              }
              enum suspended {
                value 2;
                description
                  "Receiver state is suspended, so the publisher 
                  is currently unable to provide notification messages 
                  for the subscription.";
              }
              enum connecting {
                value 3;
                if-feature "configured";
                description
                  "A subscription has been configured, but a 
                  subscription-started state change notification needs  
                  to be successfully received before notification 
                  messages are sent.";
              }
              enum timeout {
                value 4;
                if-feature "configured";
                description
                  "A subscription has failed in sending a subscription
                  started state change to the receiver.  
                  Additional attempts at connection attempts are not 
                  currently being made.";
              }
            }
            config false;
            mandatory true;
            description
              "Specifies the state of a subscription from the 
              perspective of a particular receiver.  With this info it 
              is possible to determine whether a subscriber is currently
              generating notification messages intended for that 
              receiver.";
          }
          action reset {
            description
              "Allows the reset of this configured subscription receiver
              to the 'connecting' state. This enables the
              connection process to be reinitiated.";
            output {
              leaf time {
                type yang:date-and-time;
                mandatory true;
                description
                  "Time a publisher returned the receiver to a
                  connecting state.";
              }
            }
          }          
        }
      }
    }
  }
}
